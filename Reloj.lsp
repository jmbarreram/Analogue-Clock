(defun ent_getter (h / x y l)
  (setq x (handent h))
  (setq y (entget x))
  (setq l (list x y))
)

(defun td_T (/ l ll)
  (setq l (list T))
  (repeat 6
    (setq l (append l (list T)))
  )
  (setq ll l)
)

(defun SubstNth ( a n l / i )                               ;;Lee Mac LM:SubstNth found in http://lee-mac.com/substn.html
  (setq i -1)
  (mapcar '(lambda ( x ) (if (= (setq i (1+ i)) n) a x)) l)
)

(defun on (x y i / l)
  (if (not (nth i y))
    (progn
      (setq y (SubstNth T i y))
      (redraw (nth 0 (nth i x)) 1)
    )
  )
  (setq l y)
)

(defun off (x y i / l)
  (if (nth i y)
    (progn
      (setq y (SubstNth nil i y))
      (redraw (nth 0 (nth i x)) 2)
    )
  )
  (setq l y)
)

(defun disp (x y c / l)
  (cond
    ((= c 0)
      (setq y (on x y 0))
      (setq y (on x y 1))
      (setq y (on x y 2))
      (setq y (off x y 3))
      (setq y (on x y 4))
      (setq y (on x y 5))
      (setq y (on x y 6))
     
    )
    ((= c 1)
      (setq y (off x y 0))
      (setq y (on x y 1))
      (setq y (on x y 2))
      (setq y (off x y 3))
      (setq y (off x y 4))
      (setq y (off x y 5))
      (setq y (off x y 6))
    )
    ((= c 2)
      (setq y (on x y 0))
      (setq y (off x y 1))
      (setq y (on x y 2))
      (setq y (on x y 3))
      (setq y (on x y 4))
      (setq y (on x y 5))
      (setq y (off x y 6))
    )
    ((= c 3)
      (setq y (on x y 0))
      (setq y (on x y 1))
      (setq y (on x y 2))
      (setq y (on x y 3))
      (setq y (on x y 4))
      (setq y (off x y 5))
      (setq y (off x y 6))
    )
    ((= c 4)
      (setq y (off x y 0))
      (setq y (on x y 1))
      (setq y (on x y 2))
      (setq y (on x y 3))
      (setq y (off x y 4))
      (setq y (off x y 5))
      (setq y (on x y 6))
    )
    ((= c 5)
      (setq y (on x y 0))
      (setq y (on x y 1))
      (setq y (off x y 2))
      (setq y (on x y 3))
      (setq y (on x y 4))
      (setq y (off x y 5))
      (setq y (on x y 6))
    )
    ((= c 6)
      (setq y (on x y 0))
      (setq y (on x y 1))
      (setq y (off x y 2))
      (setq y (on x y 3))
      (setq y (on x y 4))
      (setq y (on x y 5))
      (setq y (on x y 6))
    )
    ((= c 7)
      (setq y (off x y 0))
      (setq y (on x y 1))
      (setq y (on x y 2))
      (setq y (off x y 3))
      (setq y (on x y 4))
      (setq y (off x y 5))
      (setq y (off x y 6))
    )
    ((= c 8)
      (setq y (on x y 0))
      (setq y (on x y 1))
      (setq y (on x y 2))
      (setq y (on x y 3))
      (setq y (on x y 4))
      (setq y (on x y 5))
      (setq y (on x y 6))
    )
    ((= c 9)
      (setq y (on x y 0))
      (setq y (on x y 1))
      (setq y (off x y 2))
      (setq y (on x y 3))
      (setq y (on x y 4))
      (setq y (on x y 5))
      (setq y (on x y 6))
    )
    (setq l y)
  )
  (setq l y)
)

(defun reloj_d (td0 td1 td1s td10 td10s / dec uni l)
  (setq uni (rem td0 10))
  (setq dec (/ (- td0 uni) 10))
  (setq td1s (disp td1 td1s uni))
  (setq td10s (disp td10 td10s dec))
  (setq l (append (list td1s) (list td10s)))
)

(setq y (ent_getter "172B"))
(setq me (ent_getter "172A"))
(setq d (ent_getter "1729"))

(setq ye (nth 1 y))
(setq mes (nth 1 me))
(setq di (nth 1 d))

(setq tdm1 (list (ent_getter "1724")))
(setq tdm1 (append tdm1 (list (ent_getter "1723"))))
(setq tdm1 (append tdm1 (list (ent_getter "1722"))))
(setq tdm1 (append tdm1 (list (ent_getter "1721"))))
(setq tdm1 (append tdm1 (list (ent_getter "1720"))))
(setq tdm1 (append tdm1 (list (ent_getter "171F"))))
(setq tdm1 (append tdm1 (list (ent_getter "171E"))))

(setq tdm10 (list (ent_getter "1710")))
(setq tdm10 (append tdm10 (list (ent_getter "170F"))))
(setq tdm10 (append tdm10 (list (ent_getter "170E"))))
(setq tdm10 (append tdm10 (list (ent_getter "170D"))))
(setq tdm10 (append tdm10 (list (ent_getter "170C"))))
(setq tdm10 (append tdm10 (list (ent_getter "170B"))))
(setq tdm10 (append tdm10 (list (ent_getter "170A"))))

(setq tdh1 (list (ent_getter "16FC")))
(setq tdh1 (append tdh1 (list (ent_getter "16FB"))))
(setq tdh1 (append tdh1 (list (ent_getter "16FA"))))
(setq tdh1 (append tdh1 (list (ent_getter "16F9"))))
(setq tdh1 (append tdh1 (list (ent_getter "16F8"))))
(setq tdh1 (append tdh1 (list (ent_getter "16F7"))))
(setq tdh1 (append tdh1 (list (ent_getter "16F6"))))

(setq tdh10 (list (ent_getter "16E8")))
(setq tdh10 (append tdh10 (list (ent_getter "16E0"))))
(setq tdh10 (append tdh10 (list (ent_getter "16D8"))))
(setq tdh10 (append tdh10 (list (ent_getter "16D0"))))
(setq tdh10 (append tdh10 (list (ent_getter "16C8"))))
(setq tdh10 (append tdh10 (list (ent_getter "16C0"))))
(setq tdh10 (append tdh10 (list (ent_getter "16B8"))))

(setq s (ent_getter "1691"))
(setq h (ent_getter "1690"))
(setq m (ent_getter "168F"))

(setq tdm1s (td_T))
(setq tdm10s (td_T))
(setq tdh1s (td_T))
(setq tdh10s (td_T))

(setq krs (- 0.0 (/ pi 30.0)))
(setq krm krs)
(setq krm_s (/ krs 60.0))
(setq krh (- 0.0 (/ pi 6.0)))
(setq krh_m krm_s)

(setq seg (nth 1 s))
(setq mi (nth 1 m))
(setq hor (nth 1 h))

(while T
 (command "delay" "1000" )
 (setq time (rtos (getvar "cdate") 2 8))
 (setq ta (atoi (substr time 1 4)))
 (setq tme (atoi (substr time 5 2)))
 (setq td (atoi (substr time 7 2)))
 (setq th (atoi (substr time 10 2)))
 (setq tm (atoi (substr time 12 2)))
 (setq ts (atoi (substr time 14 2)))
 (if (< (strlen time) 13)
   (setq tm (* tm 10))
   (if (< (strlen time) 15)
     (setq ts (* ts 10))
   )
 )
 
 (setq rs (* ts krs))
 (setq rm (+ (* tm krm) (* ts krm_s)))
 (setq rh (+ (* th krh) (* tm krh_m)))
 
 (setq seg (subst (cons 50 rs) (assoc 50 seg) seg))
 (setq hor (subst (cons 50 rh) (assoc 50 hor) hor))
 (setq mi (subst (cons 50 rm) (assoc 50 mi) mi))

 (setq l (reloj_d tm tdm1 tdm1s tdm10 tdm10s))
 (setq tdm1s (nth 0 l))
 (setq tdm10s (nth 1 l))
 (setq l (reloj_d th tdh1 tdh1s tdh10 tdh10s))
 (setq tdh1s (nth 0 l))
 (setq tdh10s (nth 1 l))

 (setq ye (subst (cons 1 (rtos ta 2 0)) (assoc 1 ye) ye))
 (setq mes (subst (cons 1 (rtos tme 2 1)) (assoc 1 mes) mes))
 (setq di (subst (cons 1 (rtos td 2)) (assoc 1 di) di))
  
 (entmod seg)
 (entmod hor)
 (entmod mi)
 (entmod ye)
 (entmod mes)
 (entmod di)
  
 (entupd (nth 0 s))
 (entupd (nth 0 h))
 (entupd (nth 0 m))
 (entupd (nth 0 y))
 (entupd (nth 0 me))
 (entupd (nth 0 d))
)
